# NGOs

## Structural Based Feasibility: To be able to be deployed in structures that sustain at least 20% of their original structure (Functional)

### Lightweight and Quick to Deploy (Functional)

### Explore Hazardous Terrain (Functional)

### 30 Second Deploy Time (Functional)

## Modularity: To support multiple playloads (Functional)

### Support carriage for small to medium-sized items (Functional)

### Versatile Consolidated Actuation (Functional)

## Patient Care: To be able to detect and analyze patient status (Functional)

### Assess Health of the Patient (Functional)

### Patient Comfort (Functional)

## S&R Assistance: To provide rapid aid and detailed analysis for S&R responders (Functional)

### Localizations Technologies (Functional)

### Low-cost (Functional)

### Remote Visual Feedback (Functional)

### Measuring Environment Data (Functional)
